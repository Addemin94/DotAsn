-- A small UPER sensor protocol with information objects.
Sensor-Protocol DEFINITIONS AUTOMATIC TAGS ::=
BEGIN

MESSAGE ::= CLASS {
    &id       INTEGER (0..255) UNIQUE,
    &Body
} WITH SYNTAX { ID &id BODY &Body }

Messages MESSAGE ::= {
    { ID 1 BODY Measurement } |
    { ID 2 BODY Alarm },
    ...
}

Frame ::= SEQUENCE {
    id          MESSAGE.&id ({Messages}),
    body        MESSAGE.&Body ({Messages}{@id})
}

Measurement ::= SEQUENCE {
    sensor      INTEGER (0..1023),
    timestamp   INTEGER (0..4294967295),
    values      SEQUENCE (SIZE (1..8)) OF INTEGER (-32768..32767)
}

Alarm ::= SEQUENCE {
    sensor      INTEGER (0..1023),
    severity    ENUMERATED { low, high, critical },
    text        UTF8String (SIZE (0..64)) OPTIONAL
}

END
