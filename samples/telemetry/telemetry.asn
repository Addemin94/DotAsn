-- An example UPER protocol for battery-powered telemetry devices, written for the DotAsn samples.
-- It exercises the features typical of compact device protocols: constrained integers, extensible
-- enumerations, sequences and choices, extension addition groups, DEFAULT values, SIZE constraints,
-- named bits and nested collections.
Telemetry-Protocol DEFINITIONS AUTOMATIC TAGS ::=
BEGIN

MessageType ::= ENUMERATED {
    heartbeat (1),
    timeSyncRequest (2),
    timeSyncResponse (3),
    measurementReport (10),
    measurementBatch (11),
    configurationQuery (20),
    configurationReport (21),
    firmwareChunk (30),
    ...
}

-- Periodic liveness message.
Heartbeat ::= SEQUENCE {
    sequenceNumber  INTEGER (0..255),
    uptimeSeconds   INTEGER (0..4294967295)  -- seconds since boot
}

TimeSyncRequest ::= SEQUENCE {
    requestId       INTEGER (0..255),
    deviceTime      INTEGER (0..4294967295)
}

TimeSyncResponse ::= SEQUENCE {
    requestId       INTEGER (0..255),
    serverTime      INTEGER (0..4294967295),
    correctionMs    INTEGER (-32768..32767) DEFAULT 0
}

Position ::= SEQUENCE {
    latitude        INTEGER (-900000000..900000000),    -- 1e-7 degrees
    longitude       INTEGER (-1800000000..1800000000),  -- 1e-7 degrees
    altitudeM       INTEGER (-1000..10000) OPTIONAL,
    accuracyM       INTEGER (0..65535) OPTIONAL
}

Measurement ::= SEQUENCE {
    timestamp       INTEGER (0..4294967295),
    temperature     INTEGER (-400..1250) OPTIONAL,       -- 0.1 degrees Celsius
    humidity        INTEGER (0..100) OPTIONAL,
    batteryMv       INTEGER (0..5000),
    position        Position OPTIONAL,
    ...,
    [[ pressurePa   INTEGER (30000..110000) OPTIONAL ]]
}

MeasurementBatch ::= SEQUENCE {
    deviceId        OCTET STRING (SIZE (8)),
    measurements    SEQUENCE (SIZE (1..32)) OF Measurement
}

ReportingMode ::= ENUMERATED { periodic, onChange, onDemand, ... }

Configuration ::= SEQUENCE {
    mode            ReportingMode DEFAULT periodic,
    intervalSeconds INTEGER (10..86400) DEFAULT 900,
    sensorsEnabled  BIT STRING { temperature (0), humidity (1), position (2), pressure (3) } (SIZE (4)),
    label           UTF8String (SIZE (0..32)) OPTIONAL,
    ...
}

ConfigurationQuery ::= SEQUENCE {
    requestId       INTEGER (0..255),
    keys            SEQUENCE (SIZE (0..16)) OF VisibleString (SIZE (1..16)) OPTIONAL
}

FirmwareChunk ::= SEQUENCE {
    imageId         INTEGER (0..65535),
    offset          INTEGER (0..16777215),
    data            OCTET STRING (SIZE (1..512)),
    last            BOOLEAN
}

Payload ::= CHOICE {
    heartbeat           Heartbeat,
    timeSyncRequest     TimeSyncRequest,
    timeSyncResponse    TimeSyncResponse,
    measurementReport   Measurement,
    measurementBatch    MeasurementBatch,
    configurationQuery  ConfigurationQuery,
    configurationReport Configuration,
    firmwareChunk       FirmwareChunk,
    ...
}

Message ::= SEQUENCE {
    protocolVersion INTEGER (1..15) DEFAULT 1,
    messageType     MessageType,
    payload         Payload,
    crc             OCTET STRING (SIZE (4)) OPTIONAL
}

END
